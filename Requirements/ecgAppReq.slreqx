# ecgAppReq
ECG Classification App requirements

## #1: Patient data must be stored a structure (Functional)
Patients must be represented by a structure object. Implement a function that takes patient's data as input arguments and returns a structure containing such information. Assertions must be used to verify integrity of inputs.

### #2: First/last names must be alphabetic (Functional)
Patient's first and last name must be valid alphabetic char arrays or strings or a combination of them. Non-alphabetic characters are not allowed.

### #3: Age must be between 0 and 150 (Functional)
Patient's age must be between 0 and 150 years. Negative and non-integer numbers are not allowed.

### #4: Patient ID must be greater than 0 (Functional)
Patient ID must be an integer greater than 0. A patient's ID must be unique.

### #5: Frequency must be a positive integer (Functional)
ECG signal frequency must be a positive integer number.

### #6: ECG signal integrity (Functional)
ECG signal must be valid and have a minimum length of 30 seconds.

## #7: Breath rate calculation (Functional)
Calculate a patient's breath rate by performing wave decomposition on and normalizing ECG signal.

### #8: Test valid bounds (Functional)
Breath rate must be between 8 and 25 bps; otherwise, return -1

### #9: Equivalent results from C library (Functional)
Breath rate calculation must be compiled as a static C library. Relative error of output calculations must be less than 1E-6 compared to MATLAB's original function.

### #10: Minimum distance between peaks (Functional)
Peaks from input ECG signal must have at least 300 samples between them

### #11: Wave conditioning (Functional)
Use MATLAB to decompose and reconstruct input ECG signal for breath rate calculations

## #12: Heart rate calculation (Functional)
Implement MATLAB's signal detrending algorithm to condition input ECG for heart rate calculation.

### #13: Minimum distance between peaks (Functional)
Peaks from input ECG signal must have a minimum of 50 samples in between.

### #14: Minimum peak height (Functional)
After detrending and normalizing the signal, peaks must be at least 0.3 in absolute height.

### #15: Equivalent results from C library (Functional)
Heart rate calculation should be exported as a static C library. The relative error between results from this library and the original MATLAB function must not be greater than 1E-6.

### #16: Test valid bounds (Functional)
Heart rate calculation should return an output between 50 and 200 bpm.

## #17: Heart condition classifier (Functional)

### #19: Use pre-trained deep learning network (Functional)
Use alexnet to train the network with new scalograms from the test set.

### #20: Convert input ECG signal to scalogram (Functional)

### #21: Parallel processing architecture (Functional)
Deep learning classification algorithm must be capable of running on either multi-core CPUs or GPUs.

### #22: Classification algorithm must be verified (Functional)
Classification algorithm must be compared against a cross-validation set of ECG signals with labeled heart conditions.
